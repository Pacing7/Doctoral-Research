// Stakeholder definition
part def 'Systems Engineering';
part def 'Systems Safety Engineering';
part def 'Human System Integration';
part def 'Cybersecurity';
// Concern definition
// systems engineering
library package stakeholders {
concern 'Systems engineering activities' {
doc /*
* Design Engineers execute daily engineering activities to meet customer needs. 
*/


// systems safety engineering

stakeholder 'Systems Safety Engineering';

// human system integration


stakeholder 'Human System Integration';

// cybersecurity


stakeholder 'Cybersecurity';
}
}
